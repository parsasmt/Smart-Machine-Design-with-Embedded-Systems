# Requirements

## 1: Barrier alert (Functional)
Activate/Deactivate the alert on the 160 mark.

## 1: Alart performance (Informational)
Make sure it works on time.

## 4: Seat belt alarm (Functional)
Activate/Deactivate alarm based on whether the car in moving or not and if the seat belt is already fasten or not.

## 4: Door alarm (Functional)
Activate/Deactivate the alarm based on the door's position.

## 4: Alarm performance (Informational)
Make sure not to have the error that if every condition is met and the alarm goes off.

## 5: Battery reduction function (Functional)
Make a function to reduce battery over time.

## 5: Battery reduction performace (Informational)
The threshhold is as same as the day one.

## 6: Battery alarm (Functional)
Activate/Deactivate battery alarm on 20%.

## 7: Car lights (Functional)
Activate/Deactivate the cars lights based on the ambiant light.

## 7: Car lights brightness level (Informational)
The brightness level can be changed based on outside light.

## 2: Calculate speed (Functional)
Calculate the current speed based on our encoder input every 3 seconds.

## 2: Chage speed (Functional)
After calculating the speed, if needed, accelerate or decelerate.

## 2: Breaking system (Functional)
Change the braking power and speed based on the alarm we got from the distance alert.

## 3: Deciding moving direction (Functional)
If the car is moving, it should decide based in IR input which direction to move.

## 2: State 2 performance (Informational)
The outputs should be real-time, and the braking system should be safe and reliable for passengers.

## 3: Deciding moving direction performance (Informational)
The decision-making process should not take long and should be safe and reliable.
